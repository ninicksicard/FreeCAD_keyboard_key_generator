"""
batch_keycaps_export_stl_ui.FCMacro

Batch-generate per-key STL files from a selected blank key object in the current document.
"""

import os
import sys

macro_directory = os.path.dirname(os.path.abspath(__file__))
if macro_directory not in sys.path:
    sys.path.insert(0, macro_directory)

from keycap_exporter_run import generate_keycaps_to_stl_from_selected_template


generate_keycaps_to_stl_from_selected_template()
